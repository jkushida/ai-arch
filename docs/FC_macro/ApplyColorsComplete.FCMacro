# -*- coding: utf-8 -*-
"""
FreeCADマクロ: 材料に基づいて色を適用（可視化・視点調整付き）
使い方:
1. FreeCADでFCStdファイルを開く
2. マクロ → マクロ... → ApplyColorsComplete.FCMacro を実行
3. 自動的に色が適用され、視点も調整される
"""

import FreeCAD
import FreeCADGui as Gui
from PySide import QtGui

def get_material_from_properties(obj):
    '''オブジェクトのプロパティから材料タイプを取得'''
    if hasattr(obj, 'MaterialType'):
        return obj.MaterialType
    
    # MaterialTypeプロパティがない場合は他のプロパティを確認
    if hasattr(obj, 'Label'):
        label = obj.Label.lower()
        if 'wood' in label or '木' in label:
            return 1
        elif 'concrete' in label or 'コンクリート' in label:
            return 0
    
    return None

def apply_colors_and_view():
    '''アクティブドキュメントに色を適用し、視点を調整'''
    
    if not FreeCAD.ActiveDocument:
        QtGui.QMessageBox.warning(None, "警告", "ドキュメントが開かれていません")
        return
    
    # 木材色の定義（パーツごとに微妙に異なる色）
    wood_colors = {
        'Foundation': (0.85, 0.7, 0.5),     # 基礎（薄い黄土色）
        'Floor1': (0.9, 0.75, 0.55),        # 1階床（明るいベージュ）
        'Floor2': (0.95, 0.8, 0.6),         # 2階床（非常に薄い茶色）
        'Columns': (0.8, 0.65, 0.45),       # 柱（明るい茶色）
        'Walls': (0.75, 0.55, 0.35),        # 壁（濃い茶色）
        'RoofSlab': (0.75, 0.6, 0.4),       # 屋根（明るめの茶色）
        'Balcony': (0.85, 0.75, 0.6),       # バルコニー（薄い茶色）
        'Staircase': (0.8, 0.7, 0.55)       # 階段（明るい茶色）
    }
    concrete_color = (0.9, 0.9, 0.9)  # コンクリート（非常に明るいグレー）
    
    # 修正対象のオブジェクト
    building_parts = ['Foundation', 'Floor1', 'Floor2', 'Columns', 'Walls', 'RoofSlab', 'Balcony', 'Staircase']
    
    # デフォルト材料設定（材料情報が見つからない場合は全てコンクリート）
    default_material = 0  # 0: コンクリート
    
    FreeCAD.Console.PrintMessage("=== 材料色適用開始 ===\n")
    FreeCAD.Console.PrintMessage("プロパティから材料情報を読み取っています...\n")
    
    # 各オブジェクトの材料を確認
    material_info = {}
    for obj_name in building_parts:
        obj = FreeCAD.ActiveDocument.getObject(obj_name)
        if obj:
            material = get_material_from_properties(obj)
            if material is not None:
                material_info[obj_name] = material
                material_name = "木材" if material == 1 else "コンクリート"
                FreeCAD.Console.PrintMessage(f"  {obj_name}: {material_name}\n")
    
    applied_count = 0
    wood_count = 0
    concrete_count = 0
    unknown_count = 0
    
    for obj_name in building_parts:
        obj = FreeCAD.ActiveDocument.getObject(obj_name)
        if obj:
            if hasattr(obj, 'ViewObject') and obj.ViewObject is not None:
                
                # プロパティから材料を判定
                material = get_material_from_properties(obj)
                
                # 材料が不明な場合はコンクリートとして扱う
                if material is None:
                    material = default_material
                    FreeCAD.Console.PrintMessage(f"❓ {obj.Label}: 材料情報が見つからないため、コンクリートとして扱います\n")
                    unknown_count += 1
                
                # 材料に応じて色を設定
                try:
                    if material == 1:  # 木材
                        color = wood_colors.get(obj.Label, wood_colors.get('Walls'))
                        wood_count += 1
                    else:  # コンクリート
                        color = concrete_color
                        concrete_count += 1
                    
                    # 色を設定
                    obj.ViewObject.ShapeColor = color
                    
                    # 透明度を0に設定（不透明）
                    if hasattr(obj.ViewObject, 'Transparency'):
                        obj.ViewObject.Transparency = 0
                    
                    # 可視性を確実に設定
                    obj.ViewObject.Visibility = True
                    
                    # ツリーにも表示
                    if hasattr(obj.ViewObject, 'ShowInTree'):
                        obj.ViewObject.ShowInTree = True
                    
                    # DisplayModeをFlat Linesに設定（面の色＋エッジ線）
                    if hasattr(obj.ViewObject, 'DisplayMode'):
                        try:
                            obj.ViewObject.DisplayMode = "Flat Lines"
                        except:
                            pass
                    
                    applied_count += 1
                    material_name = "木材" if material == 1 else "コンクリート"
                    FreeCAD.Console.PrintMessage(f"✅ {obj.Label}: {material_name}色を適用 RGB{color}\n")
                    
                except Exception as e:
                    FreeCAD.Console.PrintError(f"⚠️ {obj.Label}: 色の適用中にエラー: {str(e)}\n")
            else:
                FreeCAD.Console.PrintWarning(f"⚠️ {obj_name}: ViewObjectが見つかりません\n")
        else:
            FreeCAD.Console.PrintError(f"❌ {obj_name}: オブジェクトが見つかりません\n")
    
    # GUIを更新
    if hasattr(Gui, 'updateGui'):
        Gui.updateGui()
    
    # ビューを調整（全体表示＆アイソメトリック）
    try:
        Gui.SendMsgToActiveView("ViewFit")
        Gui.activeDocument().activeView().viewIsometric()
        FreeCAD.Console.PrintMessage("\n✅ ビューを調整しました（全体表示・アイソメトリック）\n")
    except Exception as e:
        FreeCAD.Console.PrintError(f"\n⚠️ ビュー調整中にエラー: {str(e)}\n")
    
    # 結果をメッセージボックスで表示
    msg = f"=== 処理完了 ===\n\n"
    msg += f"✅ {applied_count} 個のオブジェクトの色を適用しました\n"
    msg += f"📊 内訳: 木材 {wood_count}個、コンクリート {concrete_count}個\n"
    if unknown_count > 0:
        msg += f"\n⚠️ {unknown_count}個のオブジェクトは材料情報が見つからず、\nコンクリートとして扱いました"
    
    QtGui.QMessageBox.information(None, "色付け完了", msg)
    
    FreeCAD.Console.PrintMessage(f"\n=== 処理完了 ===\n")
    FreeCAD.Console.PrintMessage(f"✅ {applied_count} 個のオブジェクトの色を適用しました\n")
    FreeCAD.Console.PrintMessage(f"📊 内訳: 木材 {wood_count}個、コンクリート {concrete_count}個\n")
    if unknown_count > 0:
        FreeCAD.Console.PrintMessage(f"⚠️  {unknown_count}個のオブジェクトは材料情報が見つからず、コンクリートとして扱いました\n")

# 実行
apply_colors_and_view()

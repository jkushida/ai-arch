# -*- coding: utf-8 -*-
"""
FreeCADマクロ: 材料に基づいて色を適用
使い方:
1. FreeCADでFCStdファイルを開く
2. マクロ → マクロ... → ApplyColors.FCMacro を実行
3. 自動的に色が適用される
"""

import FreeCAD
import FreeCADGui
from PySide import QtGui

def get_material_from_properties(obj):
    '''オブジェクトのプロパティから材料タイプを取得'''
    if hasattr(obj, 'MaterialType'):
        return obj.MaterialType
    return None

def apply_colors():
    '''アクティブドキュメントに色を適用'''
    
    if not FreeCAD.ActiveDocument:
        QtGui.QMessageBox.warning(None, "警告", "ドキュメントが開かれていません")
        return
    
    # 木材色の定義
    wood_colors = {
        'Foundation': (0.85, 0.7, 0.5),
        'Floor1': (0.9, 0.75, 0.55),
        'Floor2': (0.95, 0.8, 0.6),
        'Columns': (0.8, 0.65, 0.45),
        'Walls': (0.75, 0.55, 0.35),
        'RoofSlab': (0.75, 0.6, 0.4),
        'Balcony': (0.85, 0.75, 0.6),
        'Staircase': (0.8, 0.7, 0.55)
    }
    concrete_color = (0.9, 0.9, 0.9)
    
    building_parts = ['Foundation', 'Floor1', 'Floor2', 'Columns', 'Walls', 'RoofSlab', 'Balcony', 'Staircase']
    
    FreeCAD.Console.PrintMessage("=== 材料色適用開始 ===\n")
    applied_count = 0
    wood_count = 0
    concrete_count = 0
    
    for obj_name in building_parts:
        obj = FreeCAD.ActiveDocument.getObject(obj_name)
        if obj and hasattr(obj, 'ViewObject') and obj.ViewObject is not None:
            material = get_material_from_properties(obj)
            
            # 材料に応じて色を設定
            if material == 1:  # 木材
                color = wood_colors.get(obj.Label, wood_colors.get('Walls'))
                wood_count += 1
            else:  # コンクリート
                color = concrete_color
                concrete_count += 1
            
            # 色を適用
            obj.ViewObject.ShapeColor = color
            obj.ViewObject.Transparency = 0
            
            # DisplayModeを設定
            if hasattr(obj.ViewObject, 'DisplayMode'):
                try:
                    obj.ViewObject.DisplayMode = "Flat Lines"
                except:
                    pass
            
            applied_count += 1
            material_name = "木材" if material == 1 else "コンクリート"
            FreeCAD.Console.PrintMessage(f"✅ {obj.Label}: {material_name}色を適用\n")
    
    # ビューの調整
    try:
        FreeCADGui.ActiveDocument.ActiveView.viewIsometric()
        FreeCADGui.ActiveDocument.ActiveView.fitAll()
    except:
        pass
    
    # 結果をメッセージボックスで表示
    msg = f"色付け完了\n\n適用数: {applied_count}個\n木材: {wood_count}個\nコンクリート: {concrete_count}個"
    QtGui.QMessageBox.information(None, "完了", msg)
    
    FreeCAD.Console.PrintMessage(f"\n✅ {applied_count} 個のオブジェクトの色を適用しました\n")
    FreeCAD.Console.PrintMessage(f"📊 内訳: 木材 {wood_count}個、コンクリート {concrete_count}個\n")

# 実行
apply_colors()
